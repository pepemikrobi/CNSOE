module apn-vpn {

    namespace "http://atende.pl/rsl/nso/apn-vpn";
    prefix APN;

    import ietf-inet-types {
    prefix inet;
    }

    import tailf-common {
    prefix tailf;
    }
    import tailf-ncs {
    prefix ncs;
    }

    import tailf-ned-cisco-staros {
    prefix staros;
    }

    import tailf-ned-cisco-ios {
    prefix ios;
    }

    import tailf-ned-cisco-asa {
    prefix asa;
    }

    // the imports below are in fact duplicates, but these different namespaces are required for 'derived-from-or-self' NED validation

    import cisco-staros-cli {
        prefix cisco-staros-cli;
    }

    import cisco-ios-cli {
        prefix cisco-ios-cli;
    }

    import cisco-asa-cli {
        prefix cisco-asa-cli;
    }

    organization
    "Atende S.A.";

    contact
    "Robert Slaski
    robert.slaski@atende.pl";

    description
    "Cisco NSO quick PoC ASR5k VPN automation service";

    revision 2022-12-19 {
        description 
        " Robert Slaski:
          - Reviewed for GH";
    }

    revision 2020-05-22 {
        description 
        " Robert Slaski:
          - ASR5k IP pool work done
          - Tunnel subnet, tunnels up
          - cpe-firewall config done";
    }

    revision 2020-05-21 {
        description
        " Robert Slaski:
          - Moving ASR1k from CPE to operator core device role
          - Variable redesign
          - ASR1k work in progress";
    }

    revision 2020-05-21 {
        description 
        " Robert Slaski:
          - First wet draft of ASR5k apn service";
    }

    revision 2020-05-20 {
        description
        " Robert Slaski:
          - YANG model work in progress";
    }

    revision 2020-05-19 {
        description
        " Robert Slaski:
          - Initial placeholder";
    }

    //////////////////////////////
    // typedefs
    //////////////////////////////
    typedef service-name-type {
        tailf:info "Service name;;<name>";
        type string {
            pattern "[0-9a-zA-Z_-]{1,100}" {
                error-message "Illegal APN service name";
            }
            length "1..32" {
                error-message "APN service name too long";
            }
        }
    }

    typedef vlan-id-type {
        tailf:info "<2-4094>;;VLAN ID";
        type uint16 {
            range "2..4094" {
                error-message "VLAN ID out of range";
            }
        }
    }

    typedef bgp-asn2 {
        type string {
        pattern
            '([1-9][0-9]{0,3}|[1-5][0-9]{1,4}|6[0-4][0-9]{3}|65[0-4][0-9]{2}|655[0-2][0-9]|6553[0-5])';
        } 
    }

    typedef bgp-asn4 {
        type string {
            pattern
                '([1-9][0-9]{0,8}|199999999[0-8]|[1-3][0-9]{1,9}|4[01][0-9]{8}|42[0-8][0-9]{7}|429[0-3][0-9]{6}|4294[0-8][0-9]{5}|42949[0-5][0-9]{4}|429496[0-6][0-9]{3}|4294967[01][0-9]{2}|42949672[0-8][0-9]|429496729[0-5])';
        }
    }

    typedef bgp-asn {
        tailf:info "<1-65535>;;ASN2:index\n" + 
                    "<65536-4294967295>;;ASN4:index";
        type union {
            type bgp-asn2;
            type bgp-asn4;
        }
    }

    //////////////////////////////
    // common stuff
    //////////////////////////////
    grouping apn-service-common {

        leaf description {
            tailf:info "APN Service description";
            type string {
                length "1..128" {
                    error-message "Service description too long";
                }
            }
        }

        leaf service-id {
            tailf:info "APN service internal ID";
            type uint32;
        }

        leaf customer-name {
            tailf:info "Customer name";
            type leafref {
                path "/APN:APN/customers/customer/name";
            }
        }
    }

    //////////////////////////////
    // ASR5k VPN PoC
    //////////////////////////////

    container APN {
        tailf:info "ASR5k NSO managed services";
        tailf:cli-add-mode;

        container OMF {
            tailf:info "OMF integration settings";
            tailf:cli-add-mode;
            leaf host {
                tailf:info "OMF host";
                type string;
            }

            leaf port {
                tailf:info "OMF port (default is 8081)";
                type int16;
                default 8081;
            }

            leaf username {
                tailf:info "OMF REST API username";
                type string;
            }

            leaf password {
                tailf:info "OMF REST API encrypted password";
                type tailf:aes-cfb-128-encrypted-string;
            }
        }

        container customers {
            tailf:info "APN customers dictionary";
            tailf:cli-add-mode;

            list customer {
                tailf:info "Customer definition";
                key "name";
                unique "id";

                leaf name {
                    tailf:info "Customer name";
                    type string {
                        pattern '([0-9a-zA-Z\.]| )*' {
                            error-message "Illegal customer name";
                        }
                        length "1..100" {
                            error-message "Customer name too long";
                        }
                    }
                }

                leaf id {
                    tailf:info "Customer number";
                    type uint32;
                }

                container cpe-firewall {
                    tailf:cli-add-mode;
                    tailf:info "Customer firewall";

                    leaf node {
                        tailf:info "Customer firewall node";
                        type leafref {
                            path "/ncs:devices/ncs:device/ncs:name";
                        }
                        must "derived-from-or-self(/ncs:devices/ncs:device[ncs:name=current()]/ncs:device-type/ncs:cli/ncs:ned-id, 'cisco-asa-cli:cisco-asa-cli')";
                    }

                    container provider {
                        tailf:cli-add-mode;
                        tailf:info "Provider connectivity parameters";

                        leaf ipv4-address {
                            tailf:info "Provider connectivity address/prefix";
                            type tailf:ipv4-address-and-prefix-length;
                        }    

                        leaf vlan-id {
                            tailf:info "Provider connectivity VLAN ID";
                            type vlan-id-type;
                        }

                    }

                    container corp {
                        tailf:cli-add-mode;
                        tailf:info "Corporate connectivity parameters";

                        leaf ipv4-address {
                            tailf:info "Router to firewall subnet";
                            type tailf:ipv4-address-and-prefix-length;
                        }

                        leaf vlan-id {
                            tailf:info "Corp connectivity VLAN ID";
                            type vlan-id-type;
                        }

                        container security-policies {
                            tailf:cli-add-mode;
                            tailf:info "Corporate security policies";

                            list entry {
                                tailf:info "Customer corporate access security rules";
                                tailf:cli-suppress-mode; 
                                key entry;

                                leaf entry {
                                    tailf:info "ACE number"; 
                                    type uint16;
                                }

                                leaf ace {
                                    tailf:info "Firewall ACE rule";
                                    type string;
                                }

                            }
                        }
                    }
                }
                    
            }

        }

        list packet-node {
            tailf:info "ASR5k packet node parameters";
            key node;

            leaf node {
                type leafref {
                    path "/ncs:devices/ncs:device/ncs:name";
                }
                must "derived-from-or-self(/ncs:devices/ncs:device[ncs:name=current()]/ncs:device-type/ncs:cli/ncs:ned-id, 'cisco-staros-cli:cisco-staros-cli')";
            }

            must "apn-context != gi-context" {
                error-message "Different contexts must be selected for APN and Gi";
            }

            leaf apn-context {
                tailf:info "ASR5k context for APN placement";
                type leafref {
                    path "deref(../node)/../ncs:config/staros:context/staros:name";
                }
            }

            leaf gi-context {
                tailf:info "ASR5k context for VRF placement";
                type leafref {
                    path "deref(../node)/../ncs:config/staros:context/staros:name";
                }
            }

            leaf gi-interface {
                tailf:info "ASR5k Gi interface in Gi context";
                type leafref {
                    path "deref(../gi-context)/../staros:interface/staros:name";
                }
                must "not (deref(.)/../staros:mode)" {
                    tailf:dependency ".";
                }
                
            }
        }

        container ext-router {
            tailf:cli-add-mode;
            tailf:info "External tunnel/NAT router";

            leaf node {
                tailf:info "External router node";
                type leafref {
                    path "/ncs:devices/ncs:device/ncs:name";
                }
                must "derived-from-or-self(/ncs:devices/ncs:device[ncs:name=current()]/ncs:device-type/ncs:cli/ncs:ned-id, 'cisco-ios-cli:cisco-ios-cli')";
            }
            container bgp {
                tailf:info "BGP routing parametes";
                leaf as-number {
                    tailf:info "BGP AS number";
                    type bgp-asn;
                }
            }

            container subnets {
                tailf:info "External router IPv4 subnets";
                tailf:cli-add-mode;

                leaf ipv4-gi {
                    tailf:info "Gi connectivity prefix";
                    type tailf:ipv4-address-and-prefix-length;
                }
                // hardcoded .1q 1001 for connectivity

                leaf ipv4-internet {
                    tailf:info "Internet connectivity prefix";
                    type tailf:ipv4-address-and-prefix-length;
                }
                // hardcoded .1q 1003 for connectivity                
            }
        }

        //////////////////////////////
        // APN service
        //////////////////////////////

        list apn {
            tailf:info "APN service";
            
            uses ncs:service-data;
            ncs:servicepoint ASR-servicepoint;

            key name;

            leaf name {
                tailf:info "APN name";
                type service-name-type;

                must "../customer-name" {
                    tailf:dependency "../customer-name";
                    error-message "Customer name must be set for a service";
                }
            }

            uses apn-service-common;

            leaf node {
                tailf:info "Packet node to be used for this APN";
                type leafref {
                    path "/APN:APN/packet-node/node";
                }
            }

            leaf vrf {
                tailf:info "Customer VRF name";
                type string;
            }

            leaf tunnel-customer-ip-subnet {
                tailf:info "GRE tunnel customer VRF IPv4 subnet";
                type inet:ipv4-prefix;
            }

            leaf tunnel-transport-ip-addr {
                tailf:info "GRE tunnel transport IPv4 address";
                type inet:ipv4-address;
            }

            list ip-pool-group {
                tailf:info "Customer APN IP pool group";
                key name;

                leaf name {
                    tailf:info "IP pool group name";
                    type string;
                }

                list ip-pool {
                    tailf:cli-compact-syntax;
                    tailf:info "Customer APN IP pool";
                    key name;

                    leaf name {
                        tailf:info "IP pool name";
                        type string;
                    }

                    leaf pool {
                        tailf:info "IP pool";
                        type inet:ipv4-prefix;
                    }
                }

            }

            leaf ac-rulebase {
                tailf:info "Rulebase to be attached";
                type leafref {
                    path "/ncs:devices/ncs:device[ncs:name=current()/../node]/ncs:config/staros:active-charging/staros:service/staros:rulebase/staros:name";
                }
            }

        }

    }

}
